FME workspace TP2 - EHD MAL.fmw

Parameters:
- SourceDataset_GEOTIFF = ""https://donnees.montreal.ca/dataset/853eef5e-239a-447f-9352-2c8655cb7de1/resource/a3201b80-8d38-447e-b5ad-af50e0cfbd0e/download/mnsterrainbatiment_2015_1m_ahuntsic-cartierville.zip" "https://donnees.montreal.ca/dataset/853eef5e-239a-447f-9352-2c8655cb7de1/resource/13617729-d7b8-4221-83ed-7c05dcba331e/download/mnsterrainbatiment_2015_1m_anjou.zip" "https://donnees.montreal.ca/dataset/853eef5e-239a-447f-9352-2c8655cb7de1/resource/149e0700-ebc1-4165-b1b2-ea8bc9bd4d30/download/mnsterrainbatiment_2015_1m_baie-durfe.zip" "https://donnees.montreal.ca/dataset/853eef5e-239a-447f-9352-2c8655cb7de1/resource/71b4543e-0833-4b7f-8209-69a0c4fb0426/download/mnsterrainbatiment_2015_1m_beaconsfield.zip" "https://donnees.montreal.ca/dataset/853eef5e-239a-447f-9352-2c8655cb7de1/resource/0f33aedb-d50a-4089-b83a-c082d06ae337/download/mnsterrainbatiment_2015_1m_cote-des-neigesnotre-dame-de-grace.zip" "https://donnees.montreal.ca/dataset/853eef5e-239a-447f-9352-2c8655cb7de1/resource/46c2b677-2b39-4478-90d9-043d303bf4e7/download/mnsterrainbatiment_2015_1m_cote-saint-luc.zip" "https://donnees.montreal.ca/dataset/853eef5e-239a-447f-9352-2c8655cb7de1/resource/d7893cfb-24a7-447f-9bfa-78350cffdc51/download/mnsterrainbatiment_2015_1m_dollard-des-ormeaux.zip" "https://donnees.montreal.ca/dataset/853eef5e-239a-447f-9352-2c8655cb7de1/resource/9593de25-f4a9-4671-bc5d-3ffa8c32f946/download/mnsterrainbatiment_2015_1m_dorval.zip" "https://donnees.montreal.ca/dataset/853eef5e-239a-447f-9352-2c8655cb7de1/resource/7fe31b56-569f-42fb-ba4c-d0251e44c5b1/download/mnsterrainbatiment_2015_1m_hampstead.zip" "https://donnees.montreal.ca/dataset/853eef5e-239a-447f-9352-2c8655cb7de1/resource/9fce625b-4e5e-4a70-9b76-dbfcdc81dcff/download/mnsterrainbatiment_2015_1m_ile-bizardsainte-genevieve.zip" "https://donnees.montreal.ca/dataset/853eef5e-239a-447f-9352-2c8655cb7de1/resource/3f86b228-6526-4772-a15d-6439aa1f382a/download/mnsterrainbatiment_2015_1m_kirkland.zip" "https://donnees.montreal.ca/dataset/853eef5e-239a-447f-9352-2c8655cb7de1/resource/a44f65ec-dbeb-4025-9834-48e8daa11d9a/download/mnsterrainbatiment_2015_1m_lachine.zip" "https://donnees.montreal.ca/dataset/853eef5e-239a-447f-9352-2c8655cb7de1/resource/81d8f266-90a3-4709-a29d-96fc70d224c9/download/mnsterrainbatiment_2015_1m_lasalle.zip" "https://donnees.montreal.ca/dataset/853eef5e-239a-447f-9352-2c8655cb7de1/resource/42aa8447-f30c-4467-83a1-360bfd1cb12d/download/mnsterrainbatiment_2015_1m_mercierhochelaga-maisonneuve.zip" "https://donnees.montreal.ca/dataset/853eef5e-239a-447f-9352-2c8655cb7de1/resource/739b743f-7917-4812-acd0-e98e221a9678/download/mnsterrainbatiment_2015_1m_montreal-est.zip" "https://donnees.montreal.ca/dataset/853eef5e-239a-447f-9352-2c8655cb7de1/resource/ad3f35aa-5ced-41d9-8fb6-c3c42cf7fe32/download/mnsterrainbatiment_2015_1m_montreal-nord.zip" "https://donnees.montreal.ca/dataset/853eef5e-239a-447f-9352-2c8655cb7de1/resource/c2563b62-3853-405f-a13a-36ceaab24970/download/mnsterrainbatiment_2015_1m_montreal-ouest.zip" "https://donnees.montreal.ca/dataset/853eef5e-239a-447f-9352-2c8655cb7de1/resource/60035518-e650-4704-81d3-ddd9d3664fea/download/mnsterrainbatiment_2015_1m_mont-royal.zip" "https://donnees.montreal.ca/dataset/853eef5e-239a-447f-9352-2c8655cb7de1/resource/de7bb036-60c6-48a1-b44c-0f50b84fe1cf/download/mnsterrainbatiment_2015_1m_outremont.zip" "https://donnees.montreal.ca/dataset/853eef5e-239a-447f-9352-2c8655cb7de1/resource/d94f0537-0977-4aeb-a2b6-8e488e318d68/download/mnsterrainbatiment_2015_1m_pierrefonds-roxboro.zip" "https://donnees.montreal.ca/dataset/853eef5e-239a-447f-9352-2c8655cb7de1/resource/9b9274ca-9d40-4e8a-bd67-7ca0e19a212e/download/mnsterrainbatiment_2015_1m_plateau-mont-royal.zip" "https://donnees.montreal.ca/dataset/853eef5e-239a-447f-9352-2c8655cb7de1/resource/9ea6cc61-8f00-4f34-9ecc-c69d42dbe127/download/mnsterrainbatiment_2015_1m_pointe-claire.zip" "https://donnees.montreal.ca/dataset/853eef5e-239a-447f-9352-2c8655cb7de1/resource/c70a6ce0-bf37-4f99-b482-df1adc3874ca/download/mnsterrainbatiment_2015_1m_riviere-des-prairiespointe-aux-trembles.zip" "https://donnees.montreal.ca/dataset/853eef5e-239a-447f-9352-2c8655cb7de1/resource/dbf18351-bde0-4cb5-9688-54262c436e0e/download/mnsterrainbatiment_2015_1m_rosemontpetite-patrie.zip" "https://donnees.montreal.ca/dataset/853eef5e-239a-447f-9352-2c8655cb7de1/resource/d2e0ccdc-7941-4ce2-8b24-0125223718c0/download/mnsterrainbatiment_2015_1m_sainte-anne-de-bellevue.zip" "https://donnees.montreal.ca/dataset/853eef5e-239a-447f-9352-2c8655cb7de1/resource/39c5bb79-756c-42da-b9ad-ac61e1d788b9/download/mnsterrainbatiment_2015_1m_saint-laurent.zip" "https://donnees.montreal.ca/dataset/853eef5e-239a-447f-9352-2c8655cb7de1/resource/a198d9e0-49ed-4c0d-9662-a5390eef794c/download/mnsterrainbatiment_2015_1m_saint-leonard.zip" "https://donnees.montreal.ca/dataset/853eef5e-239a-447f-9352-2c8655cb7de1/resource/c2a925c7-bd84-4193-bc4b-4f2490245ce4/download/mnsterrainbatiment_2015_1m_senneville.zip%22" "https://donnees.montreal.ca/dataset/853eef5e-239a-447f-9352-2c8655cb7de1/resource/17aaf21a-b364-462b-ada3-ca8cf7b1d24f/download/mnsterrainbatiment_2015_1m_sud-ouest.zip" "https://donnees.montreal.ca/dataset/853eef5e-239a-447f-9352-2c8655cb7de1/resource/59765ec2-1368-41ec-a25d-cf4d4304236f/download/mnsterrainbatiment_2015_1m_verdun.zip" "https://donnees.montreal.ca/dataset/853eef5e-239a-447f-9352-2c8655cb7de1/resource/5a6441e3-f71f-4f34-a8ad-27fc3a29107a/download/mnsterrainbatiment_2015_1m_ville-marie.zip" "https://donnees.montreal.ca/dataset/853eef5e-239a-447f-9352-2c8655cb7de1/resource/195c7d32-df34-4ecf-8908-88c2eb0f867c/download/mnsterrainbatiment_2015_1m_villeraysaint-michelparc-extension.zip" "https://donnees.montreal.ca/dataset/853eef5e-239a-447f-9352-2c8655cb7de1/resource/db09a96e-6fc0-4659-bddb-240f8bd82723/download/mnsterrainbatiment_2015_1m_westmount.zip""   # Source GeoTIFF File(s) or URL(s)
- SourceDataset_GEOJSON_7 = https://donnees.montreal.ca/dataset/9bf7932b-2723-4a74-9c34-eb868a0c692f/resource/0bb23d95-94f3-407c-a8ba-802365940778/download/noeud.json   # Source GeoJSON File or URL
- SourceDataset_GEOJSON_6 = https://donnees.montreal.ca/dataset/984f7a68-ab34-4092-9204-4bdfcca767c5/resource/9d3d60d8-4e7f-493e-8d6a-dcd040319d8d/download/geobase.json   # Source GeoJSON File or URL
- SourceDataset_GEOJSON = https://donnees.montreal.ca/dataset/584de76b-13b9-47ea-af12-0c37b8eb5de5/resource/7c521d09-7e84-4759-856e-b5a04b95330a/download/comptages_vehicules_cyclistes_pietons.geojson   # Source GeoJSON File or URL
- DestDataset_OGCGEOPACKAGE_9 = D:\Marco\TP1_MALevesque\TP2 - EHD MAL\Fichiers TP2\Fichiers QGIS\troncons_avec_comptes.gpkg   # GeoPackage File
- DestDataset_OGCGEOPACKAGE_11 = $(FME_MF_DIR)troncons_avec_comptes.gpkg   # GeoPackage File
- DestDataset_OGCGEOPACKAGE = $(FME_MF_DIR)troncons_avec_comptes.gpkg   # GeoPackage File
- SourceDataset_GEOJSON_8 = https://donnees.montreal.ca/dataset/b628f1da-9dc3-4bb1-9875-1470f891afb1/resource/92cb062a-11be-4222-9ea5-867e7e64c5ff/download/limites-terrestres.geojson   # Source GeoJSON File or URL
- DestDataset_OGCGEOPACKAGE_8 = $(FME_MF_DIR)troncons_avec_comptes.gpkg   # GeoPackage File
- SourceDataset_SHAPEFILE = https://donnees.montreal.ca/dataset/ead1ac6f-f37c-4326-a9b9-4508d94bbc45/resource/73d4571c-fd7a-465a-aa19-05c3b24222cc/download/hydrographie-2020.zip   # Source Esri Shapefile(s)
- DestDataset_OGCGEOPACKAGE_10 = $(FME_MF_DIR)troncons_avec_comptes.gpkg   # GeoPackage File
- SourceDataset_SHAPEFILE_3 = https://donnees.montreal.ca/dataset/9797a946-9da8-41ec-8815-f6b276dec7e9/resource/e8bea324-044c-4544-bbd1-2e0d08a24216/download/limites-administratives-agglomeration-nad83.zip   # Source Esri Shapefile(s)
- DestDataset_OGCGEOPACKAGE_7 = $(FME_MF_DIR)troncons_avec_comptes.gpkg   # GeoPackage File
- DestDataset_POSTGIS = GEO7630H24   # Connection

Readers:
- GEOTIFF_1: GEOTIFF from $(SourceDataset_GEOTIFF) in CSRS.MTM-8
- GEOJSON_1: GEOJSON from $(SourceDataset_GEOJSON)
- GEOJSON_3: GEOJSON from $(SourceDataset_GEOJSON_7)
- GEOJSON_4: GEOJSON from $(SourceDataset_GEOJSON_6)
- GEOJSON_5: GEOJSON from $(SourceDataset_GEOJSON_8)
- SHAPEFILE_1: SHAPEFILE from $(SourceDataset_SHAPEFILE)
- SHAPEFILE_2: SHAPEFILE from $(SourceDataset_SHAPEFILE_3)

Writers:
- OGCGEOPACKAGE_1: OGCGEOPACKAGE to $(DestDataset_OGCGEOPACKAGE)
- OGCGEOPACKAGE_2: OGCGEOPACKAGE to $(DestDataset_OGCGEOPACKAGE_9)
- OGCGEOPACKAGE_4: OGCGEOPACKAGE to $(DestDataset_OGCGEOPACKAGE_11)
- OGCGEOPACKAGE_5: OGCGEOPACKAGE to $(DestDataset_OGCGEOPACKAGE_8)
- OGCGEOPACKAGE_6: OGCGEOPACKAGE to $(DestDataset_OGCGEOPACKAGE_10)
- OGCGEOPACKAGE_3: OGCGEOPACKAGE to $(DestDataset_OGCGEOPACKAGE_7)
- POSTGIS_1: POSTGIS to $(DestDataset_POSTGIS)

comptages_vehicules_cyclistes_pietons (reader GEOJSON_1)
    attributes: Id_Reference int, Id_Intersection int, Nom_Intersection string, Date string, Periode string, Heure int, Minute int, Seconde int, Code_Banque int, Description_Code_Banque string, NBLT int, NBT int, NBRT int, SBLT int, SBT int, SBRT int, EBLT int, EBT int, EBRT int, WBLT int, WBT int, WBRT int, Approche_Nord int, Approche_Sud int, Approche_Est int, Approche_Ouest int, Localisation_X float, Localisation_Y float, Longitude float, Latitude float
    -> Reprojector_4
Reprojector_4
    DEST = EPSG:32188
    INTERPOLATION_TYPE_NAME = Nearest Neighbor
    RASTER_CELL_SIZE = Preserve Cells
    RASTER_TOLERANCE = 0.0
    REPROJECTED -> Tester_Pietons
Tester_Pietons
    BOOL_OP = OR
    TEST_CLAUSE = TEST @Value(Description_Code_Banque) = Pietons
    TEST_MODE = TEST
    PASSED -> StatisticsCalculator_2
    FAILED -> vers_nose
Reprojector_2
    DEST = EPSG:3857
    INTERPOLATION_TYPE_NAME = Nearest Neighbor
    RASTER_CELL_SIZE = Preserve Cells
    RASTER_TOLERANCE = 0.0
    REPROJECTED -> feux_positions (writer POSTGIS_1)
    REPROJECTED -> feux_position (writer OGCGEOPACKAGE_4)
Reprojector_6
    DEST = EPSG:3857
    INTERPOLATION_TYPE_NAME = Nearest Neighbor
    RASTER_CELL_SIZE = Preserve Cells
    RASTER_TOLERANCE = 0.0
    REPROJECTED -> troncons_compte_pietons (writer OGCGEOPACKAGE_2)
    REPROJECTED -> troncons_compte_pietons (writer POSTGIS_1)
Reprojector_7
    DEST = EPSG:3857
    INTERPOLATION_TYPE_NAME = Nearest Neighbor
    RASTER_CELL_SIZE = Preserve Cells
    RASTER_TOLERANCE = 0.0
    REPROJECTED -> Voiture
    REPROJECTED -> Camion
    REPROJECTED -> Bus
    REPROJECTED -> Vélo
Reprojector_10
    DEST = EPSG:3857
    INTERPOLATION_TYPE_NAME = Nearest Neighbor
    RASTER_CELL_SIZE = Preserve Cells
    RASTER_TOLERANCE = 0.0
    REPROJECTED -> hydro (writer POSTGIS_1)
    REPROJECTED -> hydrographie (writer OGCGEOPACKAGE_6)
Reprojector_9
    DEST = EPSG:3857
    INTERPOLATION_TYPE_NAME = Nearest Neighbor
    RASTER_CELL_SIZE = Preserve Cells
    RASTER_TOLERANCE = 0.0
    REPROJECTED -> arrondissements (writer POSTGIS_1)
    REPROJECTED -> arrondissements_montreal (writer OGCGEOPACKAGE_3)
Reprojector_8
    DEST = EPSG:3857
    INTERPOLATION_TYPE_NAME = Nearest Neighbor
    RASTER_CELL_SIZE = Preserve Cells
    RASTER_TOLERANCE = 0.0
    REPROJECTED -> ile_montreal (writer POSTGIS_1)
    REPROJECTED -> ile_montreal (writer OGCGEOPACKAGE_5)

Bookmark: Piétons (n'ont pas de XBT, XBRT, XBLT, mais plutôt des approches. Nécessite un traitement différent
Note: Somme les données de traffic par Id_intersection, date, heure, type de transport
StatisticsCalculator_2
    CALCULATION_MODE = NUMERIC
    FEAT_STATS = Approche_Nord,NUMERIC_MODE,,,,SUM,,,,,,,,,;Approche_Ouest,NUMERIC_MODE,,,,SUM,,,,,,,,,;Approche_Sud,NUMERIC_MODE,,,,SUM,,,,,,,,,;Approche_Est,NUMERIC_MODE,,,,SUM,,,,,,,,,
    GROUP_BY = Id_Intersection Nom_Intersection Date Heure Description_Code_Banque Code_Banque
    SUMMARY -> FeatureMerger_2 [REQUESTOR]
    COMPLETE -> AttributeManager_3
AttributeManager_3
    ATTR_TABLE:
      REMOVE Id_Reference
      REMOVE Periode
      REMOVE Minute
      REMOVE Seconde
      REMOVE NBLT
      REMOVE NBT
      REMOVE NBRT
      REMOVE SBLT
      REMOVE SBT
      REMOVE SBRT
      REMOVE EBLT
      REMOVE EBT
      REMOVE EBRT
      REMOVE WBLT
      REMOVE WBT
      REMOVE WBRT
      REMOVE Approche_Nord
      REMOVE Approche_Sud
      REMOVE Approche_Est
      REMOVE Approche_Ouest
      REMOVE Longitude
      REMOVE Latitude
    -> FeatureMerger_2 [SUPPLIER]
FeatureMerger_2
    GROUP_BY = Code_Banque Date Description_Code_Banque Heure Id_Intersection Nom_Intersection
    JOIN_KEYS = @Value(Id_Intersection) @Value(Id_Intersection) AUTO
    MERGE_TYPE = Geometry
    PROCESS_DUPS = NO
    REJECT_NULL_MISSING_KEYS = No
    SUPPLIERS_FIRST = No
    MERGED -> AttributeRenamer_2
AttributeRenamer_2
    ATTR_TABLE:
      RENAME_SET_DEFAULT Approche_Nord.sum > de_n.sum
      RENAME_SET_DEFAULT Approche_Ouest.sum > de_o.sum
      RENAME_SET_DEFAULT Approche_Sud.sum > de_s.sum
      RENAME_SET_DEFAULT Approche_Est.sum > de_e.sum
    MISSING_INPUT_ATTRS = REMOVE
    -> CoordinateExtractor_3
CoordinateExtractor_3
    IND = 0
    MODE = Specify Coordinate
    X_ATTR = _x_FEU
    Y_ATTR = _y_FEU
    -> Bufferer_3
Bufferer_3
    ANGLE = 22.5
    CAP_STYLE = Arc
    CORNER_STYLE = Arc
    MODE = AREA
    OFFSET = 15
    OFFSET_UNITS = METERS
    PRECISION = APPROX
    BUFFERED -> GeometryExtractor

Bookmark: Liste des heures
GeometryExtractor
    ATTR = _geometry
    KIND_LONG = FME Binary
    REMOVE_GEOMETRY = No
    -> ListBuilder_Données_par_heure
ListBuilder_Données_par_heure
    GROUP_BY = Date Id_Intersection Code_Banque Description_Code_Banque Nom_Intersection _x_FEU _y_FEU fme_feature_type _geometry
    LIST_ATTRS_TO_INCLUDE = Heure de_e.sum de_n.sum de_o.sum de_s.sum
    LIST_NAME = _liste_heures
    -> GeometryReplacer
GeometryReplacer
    KIND_LONG = FME Binary
    REMOVE_ATTRIBUTE = Yes
    SOURCE = @Value(_geometry)
    -> SpatialFilter_8 [Filter]

Bookmark: Attributs in-out par direction (NOSE) par intersection
vers_nose: AttributeCreator
    ATTR_TABLE:
      SET_TO vers_n = @add(
        @Value(NBT) , @Value(WBRT) , @Value(EBLT)
        )
      SET_TO vers_o = @add(
        @Value(WBT) , @Value(NBLT) , @Value(SBRT)
        )
      SET_TO vers_s = @add(
        @Value(SBT) , @Value(WBLT) , @Value(EBRT)
        )
      SET_TO vers_e = @add(
        @Value(EBT) , @Value(SBLT) , @Value(NBRT)
        )
    -> de_nose
de_nose: AttributeCreator
    ATTR_TABLE:
      SET_TO de_n = @add(
        @Value(NBT) , @Value(NBLT) , @Value(NBRT)
        )
      SET_TO de_o = @add(
        @Value(WBT) , @Value(WBLT) , @Value(WBRT)
        )
      SET_TO de_s = @add(
        @Value(SBT) , @Value(SBLT) , @Value(SBRT)
        )
      SET_TO de_e = @add(
        @Value(EBT) , @Value(EBLT) , @Value(EBRT)
        )
    -> StatisticsCalculator
StatisticsCalculator
    CALCULATION_MODE = NUMERIC
    FEAT_STATS = vers_n,NUMERIC_MODE,,,,SUM,,,,,,,,,;vers_o,NUMERIC_MODE,,,,SUM,,,,,,,,,;vers_s,NUMERIC_MODE,,,,SUM,,,,,,,,,;vers_e,NUMERIC_MODE,,,,SUM,,,,,,,,,;de_n,NUMERIC_MODE,,,,SUM,,,,,,,,,;de_o,NUMERIC_MODE,,,,SUM,,,,,,,,,;de_s,NUMERIC_MODE,,,,SUM,,,,,,,,,;de_e,NUMERIC_MODE,,,,SUM,,,,,,,,,
    GROUP_BY = Id_Intersection Nom_Intersection Date Heure Description_Code_Banque Code_Banque
    SUMMARY -> FeatureMerger [REQUESTOR]
    COMPLETE -> AttributeManager

Bookmark: On redonne leur géométrie aux statistiques
AttributeManager
    ATTR_TABLE:
      REMOVE Id_Reference
      REMOVE Periode
      REMOVE Minute
      REMOVE Seconde
      REMOVE NBLT
      REMOVE NBT
      REMOVE NBRT
      REMOVE SBLT
      REMOVE SBT
      REMOVE SBRT
      REMOVE EBLT
      REMOVE EBT
      REMOVE EBRT
      REMOVE WBLT
      REMOVE WBT
      REMOVE WBRT
      REMOVE Approche_Nord
      REMOVE Approche_Sud
      REMOVE Approche_Est
      REMOVE Approche_Ouest
      REMOVE Longitude
      REMOVE Latitude
    -> FeatureMerger [SUPPLIER]
FeatureMerger
    GROUP_BY = Code_Banque Date Description_Code_Banque Heure Id_Intersection Nom_Intersection
    JOIN_KEYS = @Value(Id_Intersection) @Value(Id_Intersection) AUTO
    MERGE_TYPE = Geometry
    PROCESS_DUPS = NO
    REJECT_NULL_MISSING_KEYS = No
    SUPPLIERS_FIRST = No
    MERGED -> DuplicateFilter
    MERGED -> CoordinateExtractor_2

Bookmark: Alléger la ointure spatial
CoordinateExtractor_2
    IND = 0
    MODE = Specify Coordinate
    X_ATTR = _x_FEU
    Y_ATTR = _y_FEU
    -> Bufferer_2
Bufferer_2
    ANGLE = 22.5
    CAP_STYLE = Arc
    CORNER_STYLE = Arc
    MODE = AREA
    OFFSET = 15
    OFFSET_UNITS = METERS
    PRECISION = APPROX
    BUFFERED -> GeometryExtractor_2
GeometryExtractor_2
    ATTR = _geometry
    KIND_LONG = FME Binary
    REMOVE_GEOMETRY = No
    -> ListBuilder_heures
GeometryReplacer_2
    KIND_LONG = FME Binary
    REMOVE_ATTRIBUTE = Yes
    SOURCE = @Value(_geometry)
    -> SpatialFilter_5 [Filter]

Bookmark: Liste dans une liste
ListBuilder_heures
    GROUP_BY = Code_Banque Date Description_Code_Banque Id_Intersection Nom_Intersection _geometry _x_FEU _y_FEU fme_feature_type
    LIST_ATTRS_TO_INCLUDE = Heure de_e.sum de_n.sum de_o.sum de_s.sum vers_e.sum vers_n.sum vers_o.sum vers_s.sum
    LIST_NAME = _liste_heures
    -> ListBuilder_2
ListBuilder_2
    GROUP_BY = Date Id_Intersection Nom_Intersection _geometry _x_FEU _y_FEU fme_feature_type
    LIST_ATTRS_TO_INCLUDE = Code_Banque Description_Code_Banque _liste_heures{}.Heure _liste_heures{}.de_e.sum _liste_heures{}.de_n.sum _liste_heures{}.de_o.sum _liste_heures{}.de_s.sum _liste_heures{}.vers_e.sum _liste_heures{}.vers_n.sum _liste_heures{}.vers_o.sum _liste_heures{}.vers_s.sum
    LIST_NAME = _liste_mode_transp
    -> GeometryReplacer_2

Bookmark: Sélection route avec feux
Note: Pour garder qu'une entitée de chaque feux de circulation
DuplicateFilter
    INPUT_ORDERED_CHOICE = No
    KEYATTR = Id_Intersection
    UNIQUE -> Bufferer
    UNIQUE -> Reprojector_2
Bufferer
    ANGLE = 22.5
    CAP_STYLE = Arc
    CORNER_STYLE = Arc
    MODE = AREA
    OFFSET = 15
    OFFSET_UNITS = METERS
    PRECISION = APPROX
    BUFFERED -> Spatial_Filter [Filter]
geobase_mtl (reader GEOJSON_4)
    attributes: ID_TRC int, DEB_GCH int, FIN_GCH int, ARR_GCH string, SENS_CIR int, CLASSE int, LIE_VOIE string, TYP_VOIE string, DIR_VOIE string, NOM_VOIE string, DEB_DRT int, FIN_DRT int, ARR_DRT string, LIM_GCH string, LIM_DRT string, POSITION int, ODONYME string
    -> Reprojector_3
Reprojector_3
    DEST = EPSG:32188
    INTERPOLATION_TYPE_NAME = Nearest Neighbor
    RASTER_CELL_SIZE = Preserve Cells
    RASTER_TOLERANCE = 0.0
    REPROJECTED -> Tester_non-autoroute
Tester_non-autoroute
    BOOL_OP = COMPOSITE
    COMPOSITE_TEST = 1 AND 2
    TEST_CLAUSE:
      TEST @Value(TYP_VOIE) != autoroute
      TEST @Value(TYP_VOIE) != voie
    TEST_MODE = TEST
    PASSED -> FeatureJoiner [LEFT]
    PASSED -> Spatial_Filter [Candidate]
Note: INERSECTS route et feux_buff
Spatial_Filter: SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> ListBuild_Nom_rues_compteurs
FeatureJoiner
    ATTR_CONFLICT_RES = Prefer Left
    GEOMETRY_HANDLING = Prefer Left
    JOIN_KEYS = ODONYME _list_ODONYME AUTO ARR_GCH ARR_GCH AUTO ARR_DRT ARR_DRT AUTO
    JOIN_MODE = Inner
    JOINED -> AreaBuilder
    JOINED -> FeatureJoiner_5 [LEFT]
    JOINED -> CoordinateExtractor

Bookmark: export geopackage local si POSTGS fontionne pas
feux_position (writer OGCGEOPACKAGE_4)
    attributes: Id_Intersection int, Nom_Intersection text, Date text, Heure int, Code_Banque int, Description_Code_Banque text, vers_n.sum double, vers_o.sum double, vers_s.sum double, vers_e.sum double, de_n.sum double, de_o.sum double, de_s.sum double, de_e.sum double
troncons_compte_pietons (writer OGCGEOPACKAGE_2)
    attributes: compte_total int, Id_Intersection int, Nom_Intersection text, Date date, _x_FEU double, _y_FEU double, Code_Banque int, Description_Code_Banque text, Heure int, vers_n.sum int, vers_o.sum int, vers_s.sum int, vers_e.sum int, de_n.sum int, de_o.sum int, de_s.sum int, de_e.sum int, ID_TRC int, DEB_GCH int, FIN_GCH int, ARR_GCH text, SENS_CIR int, CLASSE int, LIE_VOIE text, TYP_VOIE text, DIR_VOIE text, NOM_VOIE text, DEB_DRT int, FIN_DRT int, ARR_DRT text,
      LIM_GCH text, LIM_DRT text, POSITION int, ODONYME text, _list_ODONYME text, _predicate text, _orientation text(200), x.max double, y_xmax double
troncons_compte_voitures (writer OGCGEOPACKAGE_2)
    attributes: compte_total int, Id_Intersection int, Nom_Intersection text, Date date, _x_FEU double, _y_FEU double, Code_Banque int, Description_Code_Banque text, Heure int, vers_n.sum int, vers_o.sum int, vers_s.sum int, vers_e.sum int, de_n.sum int, de_o.sum int, de_s.sum int, de_e.sum int, ID_TRC int, DEB_GCH int, FIN_GCH int, ARR_GCH text, SENS_CIR int, CLASSE int, LIE_VOIE text, TYP_VOIE text, DIR_VOIE text, NOM_VOIE text, DEB_DRT int, FIN_DRT int, ARR_DRT text,
      LIM_GCH text, LIM_DRT text, POSITION int, ODONYME text, _list_ODONYME text, _predicate text, _orientation text(200), x.max double, y_xmax double
troncons_compte_camions (writer OGCGEOPACKAGE_2)
    attributes: compte_total int, Id_Intersection int, Nom_Intersection text, Date date, _x_FEU double, _y_FEU double, Code_Banque int, Description_Code_Banque text, Heure int, vers_n.sum int, vers_o.sum int, vers_s.sum int, vers_e.sum int, de_n.sum int, de_o.sum int, de_s.sum int, de_e.sum int, ID_TRC int, DEB_GCH int, FIN_GCH int, ARR_GCH text, SENS_CIR int, CLASSE int, LIE_VOIE text, TYP_VOIE text, DIR_VOIE text, NOM_VOIE text, DEB_DRT int, FIN_DRT int, ARR_DRT text,
      LIM_GCH text, LIM_DRT text, POSITION int, ODONYME text, _list_ODONYME text, _predicate text, _orientation text(200), x.max double, y_xmax double
troncons_compte_bus (writer OGCGEOPACKAGE_2)
    attributes: compte_total int, Id_Intersection int, Nom_Intersection text, Date date, _x_FEU double, _y_FEU double, Code_Banque int, Description_Code_Banque text, Heure int, vers_n.sum int, vers_o.sum int, vers_s.sum int, vers_e.sum int, de_n.sum int, de_o.sum int, de_s.sum int, de_e.sum int, ID_TRC int, DEB_GCH int, FIN_GCH int, ARR_GCH text, SENS_CIR int, CLASSE int, LIE_VOIE text, TYP_VOIE text, DIR_VOIE text, NOM_VOIE text, DEB_DRT int, FIN_DRT int, ARR_DRT text,
      LIM_GCH text, LIM_DRT text, POSITION int, ODONYME text, _list_ODONYME text, _predicate text, _orientation text(200), x.max double, y_xmax double
troncons_compte_velos (writer OGCGEOPACKAGE_2)
    attributes: compte_total int, Id_Intersection int, Nom_Intersection text, Date date, _x_FEU double, _y_FEU double, Code_Banque int, Description_Code_Banque text, Heure int, vers_n.sum int, vers_o.sum int, vers_s.sum int, vers_e.sum int, de_n.sum int, de_o.sum int, de_s.sum int, de_e.sum int, ID_TRC int, DEB_GCH int, FIN_GCH int, ARR_GCH text, SENS_CIR int, CLASSE int, LIE_VOIE text, TYP_VOIE text, DIR_VOIE text, NOM_VOIE text, DEB_DRT int, FIN_DRT int, ARR_DRT text,
      LIM_GCH text, LIM_DRT text, POSITION int, ODONYME text, _list_ODONYME text, _predicate text, _orientation text(200), x.max double, y_xmax double
hydrographie (writer OGCGEOPACKAGE_6)
    attributes: TOPONYME text(200), EQM text(40), SOURCE text(30), TRAITEMENT text(30), DIFFUSEUR text(50), VERSION mediumint, _area double
arrondissements_montreal (writer OGCGEOPACKAGE_3)
    attributes: CODEID int, NOM text(80), NOM_OFFICI text(80), CODEMAMH text(80), CODE_3C text(80), NUM int, ABREV text(80), TYPE text(80), COMMENT text(129), DATEMODIF text(80)
ile_montreal (writer OGCGEOPACKAGE_5)
    attributes: DefaultAtt text

Bookmark: Export POSTGIS
feux_positions (writer POSTGIS_1)
    attributes: id_intersection int8, nom_intersection text, date text, heure int8, code_banque int8, description_code_banque text, vers_n_sum float8, vers_o_sum float8, vers_s_sum float8, vers_e_sum float8, de_n_sum float8, de_o_sum float8, de_s_sum float8, de_e_sum float8
troncons_compte_pietons (writer POSTGIS_1)
    attributes: compte_total varchar(200), id_intersection int8, nom_intersection text, date text, code_banque int8, description_code_banque text, _x_feu float8, _y_feu float8, de_n_sum float8, de_o_sum float8, de_s_sum float8, de_e_sum float8, heure int8, id_trc int8, deb_gch int8, fin_gch int8, arr_gch text, sens_cir int8, classe int8, lie_voie text, typ_voie text, dir_voie text, nom_voie text, deb_drt int8, fin_drt int8, arr_drt text, lim_gch text, lim_drt text, position int8, odonyme text,
      _list_odonyme text, _orientation varchar(200), x_max float8, y_xmax float8, _predicate text
troncons_compte_voitures (writer POSTGIS_1)
    attributes: compte_total varchar(200), id_intersection int8, nom_intersection text, date text, _x_feu float8, _y_feu float8, code_banque int8, description_code_banque text, heure int8, vers_n_sum float8, vers_o_sum float8, vers_s_sum float8, vers_e_sum float8, de_n_sum float8, de_o_sum float8, de_s_sum float8, de_e_sum float8, id_trc int8, deb_gch int8, fin_gch int8, arr_gch text, sens_cir int8, classe int8, lie_voie text, typ_voie text, dir_voie text, nom_voie text, deb_drt int8, fin_drt int8, arr_drt text,
      lim_gch text, lim_drt text, position int8, odonyme text, _list_odonyme text, _orientation varchar(200), x_max float8, y_xmax float8
troncons_compte_camions (writer POSTGIS_1)
    attributes: compte_total varchar(200), id_intersection int8, nom_intersection text, date text, _x_feu float8, _y_feu float8, code_banque int8, description_code_banque text, heure int8, vers_n_sum float8, vers_o_sum float8, vers_s_sum float8, vers_e_sum float8, de_n_sum float8, de_o_sum float8, de_s_sum float8, de_e_sum float8, id_trc int8, deb_gch int8, fin_gch int8, arr_gch text, sens_cir int8, classe int8, lie_voie text, typ_voie text, dir_voie text, nom_voie text, deb_drt int8, fin_drt int8, arr_drt text,
      lim_gch text, lim_drt text, position int8, odonyme text, _list_odonyme text, _orientation varchar(200), x_max float8, y_xmax float8
troncons_compte_bus (writer POSTGIS_1)
    attributes: compte_total varchar(200), id_intersection int8, nom_intersection text, date text, _x_feu float8, _y_feu float8, code_banque int8, description_code_banque text, heure int8, vers_n_sum float8, vers_o_sum float8, vers_s_sum float8, vers_e_sum float8, de_n_sum float8, de_o_sum float8, de_s_sum float8, de_e_sum float8, id_trc int8, deb_gch int8, fin_gch int8, arr_gch text, sens_cir int8, classe int8, lie_voie text, typ_voie text, dir_voie text, nom_voie text, deb_drt int8, fin_drt int8, arr_drt text,
      lim_gch text, lim_drt text, position int8, odonyme text, _list_odonyme text, _orientation varchar(200), x_max float8, y_xmax float8
troncons_compte_velos (writer POSTGIS_1)
    attributes: compte_total varchar(200), id_intersection int8, nom_intersection text, date text, _x_feu float8, _y_feu float8, code_banque int8, description_code_banque text, heure int8, vers_n_sum float8, vers_o_sum float8, vers_s_sum float8, vers_e_sum float8, de_n_sum float8, de_o_sum float8, de_s_sum float8, de_e_sum float8, id_trc int8, deb_gch int8, fin_gch int8, arr_gch text, sens_cir int8, classe int8, lie_voie text, typ_voie text, dir_voie text, nom_voie text, deb_drt int8, fin_drt int8, arr_drt text,
      lim_gch text, lim_drt text, position int8, odonyme text, _list_odonyme text, _orientation varchar(200), x_max float8, y_xmax float8
hydro (writer POSTGIS_1)
    attributes: toponyme varchar(200), eqm varchar(40), source varchar(30), traitement varchar(30), diffuseur varchar(50), version int4, _area float8
arrondissements (writer POSTGIS_1)
    attributes: codeid int8, nom varchar(80), nom_offici varchar(80), codemamh varchar(80), code_3c varchar(80), num int8, abrev varchar(80), type varchar(80), comment varchar(129), datemodif varchar(80)
ile_montreal (writer POSTGIS_1)
    attributes: defaultatt text

Bookmark: Liste identifiant (ODONYME+ARR_GCH,_DRT)
ListBuild_Nom_rues_compteurs: ListBuilder
    LIST_ATTRS_TO_INCLUDE = NOM_VOIE ODONYME ARR_DRT ARR_GCH
    LIST_NAME = _rues_avec_compteurs
    -> ListeExplo_noms_rues
ListeExplo_noms_rues: ListExploder
    ATTR_ACCUM_MODE = Merge List Attributes
    ATTR_CONFLICT_RES = Use List Attribute Values
    LIST_ATTR = _rues_avec_compteurs{}
    ELEMENTS -> DuplicateFilter_2
DuplicateFilter_2
    INPUT_ORDERED_CHOICE = No
    KEYATTR = NOM_VOIE ODONYME ARR_DRT ARR_GCH
    UNIQUE -> AttributeRenamer
AttributeRenamer
    ATTR_TABLE = RENAME_SET_DEFAULT ODONYME > _list_ODONYME
    MISSING_INPUT_ATTRS = REMOVE
    -> FeatureJoiner [RIGHT]

Bookmark: Construction polygones grâce aux rues préservées (peut être utile plus tard) ???????????????????????????????????
AreaBuilder
    ALLOW_CYCLES = No
    CHECK_CURVE_DIRECTION = No
    CONNECT_Z_MODE = First Wins
    CONSIDER_NODE_ELEVATION = no
    DEAGGREGATE_INPUT = Deaggregate
    DONUT_CREATION = NO
    LINES_AS_SEGMENTS = No
    POLY_ACCUM_ATTRS_NAME = Use Attributes From One Feature
    SNAPTYPE_PARAM = End Point Snapping
    SNAP_TOLERANCE = 10
    AREA -> AreaCalculator
AreaCalculator
    AREA_ATTR = _area
    AREA_TYPE = Plane Area
    MULT = 1
    -> VertexCounter
VertexCounter
    CNT_ATTR = _vertexcount
    -> AttributeCreator
AttributeCreator
    ATTR_TABLE = SET_TO ratio_nbrvertex_aire = @mult(@div( @Value(_vertexcount),@Value(_area) ) , 100)
    -> Tester_4
Tester_4
    BOOL_OP = OR
    TEST_CLAUSE = TEST @Value(ratio_nbrvertex_aire) < 0,4
    TEST_MODE = TEST
    PASSED -> Tester_5
Tester_5
    BOOL_OP = OR
    TEST_CLAUSE = TEST @Value(_area) > 12000
    TEST_MODE = TEST

Bookmark: Calcule de dérivée géométrique
CoordinateExtractor
    LIST_NAME = _coordonnées
    MODE = All Coordinates
    -> ListExploder_coordonnées
ListExploder_coordonnées
    ATTR_ACCUM_MODE = Merge List Attributes
    ATTR_CONFLICT_RES = Use List Attribute Values
    INDEX_ATTR = _element_index
    LIST_ATTR = _coordonnées{}
    ELEMENTS -> StatisticsCalculator_x_min_
    ELEMENTS -> StatisticsCalculator__x_max_
    ELEMENTS -> FeatureJoiner__ajout_x_min [RIGHT]
    ELEMENTS -> FeatureJoiner__ajout_x_max [RIGHT]
StatisticsCalculator_x_min_
    CALCULATION_MODE = NUMERIC
    FEAT_STATS = x,NUMERIC_MODE,MIN,,,,,,,,,,,,
    GROUP_BY = ID_TRC
    SUMMARY -> FeatureJoiner__ajout_x_min [LEFT]
FeatureJoiner__ajout_x_min
    ATTR_CONFLICT_RES = Prefer Left
    GEOMETRY_HANDLING = Prefer Left
    JOIN_KEYS = ID_TRC ID_TRC AUTO x.min x AUTO
    JOIN_MODE = Inner
    JOINED -> XMIN
XMIN: AttributeManager
    ATTR_TABLE:
      REMOVE DEB_GCH
      REMOVE FIN_GCH
      REMOVE ARR_GCH
      REMOVE SENS_CIR
      REMOVE CLASSE
      REMOVE LIE_VOIE
      REMOVE TYP_VOIE
      REMOVE DIR_VOIE
      REMOVE DEB_DRT
      REMOVE FIN_DRT
      REMOVE ARR_DRT
      REMOVE LIM_GCH
      REMOVE LIM_DRT
      REMOVE POSITION
      REMOVE ODONYME
      RENAME_SET_VALUE y > y_xmin
      REMOVE z
      REMOVE _element_index
    -> FeatureJoiner_2 [LEFT]
StatisticsCalculator__x_max_
    CALCULATION_MODE = NUMERIC
    FEAT_STATS = x,NUMERIC_MODE,,MAX,,,,,,,,,,,
    GROUP_BY = ID_TRC
    SUMMARY -> FeatureJoiner__ajout_x_max [LEFT]
FeatureJoiner__ajout_x_max
    ATTR_CONFLICT_RES = Prefer Left
    GEOMETRY_HANDLING = Prefer Left
    JOIN_KEYS = ID_TRC ID_TRC AUTO x.max x AUTO
    JOIN_MODE = Inner
    JOINED -> XMAX
XMAX: AttributeManager
    ATTR_TABLE:
      REMOVE DEB_GCH
      REMOVE FIN_GCH
      REMOVE ARR_GCH
      REMOVE SENS_CIR
      REMOVE CLASSE
      REMOVE LIE_VOIE
      REMOVE TYP_VOIE
      REMOVE DIR_VOIE
      REMOVE DEB_DRT
      REMOVE FIN_DRT
      REMOVE ARR_DRT
      REMOVE LIM_GCH
      REMOVE LIM_DRT
      REMOVE POSITION
      REMOVE ODONYME
      RENAME_SET_VALUE y > y_xmax
      REMOVE z
      REMOVE _element_index
    -> FeatureJoiner_2 [RIGHT]
FeatureJoiner_2
    ATTR_CONFLICT_RES = Prefer Left
    GEOMETRY_HANDLING = Prefer Left
    JOIN_KEYS = ID_TRC ID_TRC AUTO
    JOIN_MODE = Inner
    JOINED -> AttributeCreator__DELTA_y
AttributeCreator__DELTA_y
    ATTR_TABLE = SET_TO DELTA_y = @sub(@Value(y_xmax),@Value(y_xmin))
    -> Tester__signe_DELTA_y
Tester__signe_DELTA_y
    BOOL_OP = OR
    TEST_CLAUSE = TEST @Value(DELTA_y) > 0
    TEST_MODE = TEST
    PASSED -> AttributeCreator_EW
    FAILED -> AttributeCreator_NS

Bookmark: Orientation Nord-Sud ou Est-Ouest
AttributeCreator_EW
    ATTR_TABLE = SET_TO _orientation = EW
    -> Junction
AttributeCreator_NS
    ATTR_TABLE = SET_TO _orientation = NS
    -> Junction
Junction
    -> AttributeManager_2
AttributeManager_2
    ATTR_TABLE:
      REMOVE DELTA_y
      REMOVE x.min
      REMOVE x
      REMOVE y_xmin
    -> FeatureJoiner_5 [RIGHT]
FeatureJoiner_5
    ATTR_CONFLICT_RES = Prefer Left
    GEOMETRY_HANDLING = Prefer Left
    JOIN_KEYS = ID_TRC ID_TRC AUTO
    JOIN_MODE = Inner
    JOINED -> SpatialFilter_8 [Candidate]
    JOINED -> SpatialFilter_5 [Candidate]

Bookmark: Donner attributs de décompte des feux aux tronçons adjacents
SpatialFilter_8
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> ListExploder_heures
ListExploder_heures
    ATTR_ACCUM_MODE = Merge List Attributes
    ATTR_CONFLICT_RES = Use List Attribute Values
    LIST_ATTR = _liste_heures{}
    ELEMENTS -> Tester_NS_5
Tester_NS_5
    BOOL_OP = OR
    TEST_CLAUSE = TEST @Value(_orientation) = NS
    TEST_MODE = TEST
    PASSED -> TestFilter_auN_auS
    FAILED -> TestFilter_auE_auW
Note: positions relatives des tronçons à leur feu
TestFilter_auN_auS
    DEFAULT_VALUE = au_sud_du_feu
    PASSED_TEST_GROUP_OUTPUT = FIRST
    TEST_LIST = "BOOL_OP,OR,COMPOSITE_TEST,""""""1"""""",TEST_CLAUSE,TEST @Value(y_xmax) > @sub(@Value(_y_FEU),5)",au_nord_du_feu
    au_nord_du_feu -> AttributeCreator_compteN
    au_sud_du_feu -> AttributeCreator_compteS
AttributeCreator_compteN
    ATTR_TABLE = SET_TO compte_total = @int(@Value(de_n.sum))
    -> Junction_2
AttributeCreator_compteS
    ATTR_TABLE = SET_TO compte_total = @int(@Value(de_s.sum))
    -> Junction_2
TestFilter_auE_auW
    DEFAULT_VALUE = a_ouest_du_feu
    PASSED_TEST_GROUP_OUTPUT = FIRST
    TEST_LIST = "BOOL_OP,OR,COMPOSITE_TEST,""""""1"""""",TEST_CLAUSE,TEST @Value(x.max) > @add(@Value(_x_FEU),5)",a_est_du_feu
    a_est_du_feu -> AttributeCreator_compteE
    a_ouest_du_feu -> AttributeCreator_compteW
AttributeCreator_compteE
    ATTR_TABLE = SET_TO compte_total = @int(@Value(de_e.sum))
    -> Junction_2
AttributeCreator_compteW
    ATTR_TABLE = SET_TO compte_total = @int(@Value(de_o.sum))
    -> Junction_2
Junction_2
    -> Reprojector_6
SpatialFilter_5
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDICATES = INTERSECTS
    USE_BOUNDING_BOX = No
    PASSED -> ListExploder_modetransp
ListExploder_modetransp
    ATTR_ACCUM_MODE = Merge List Attributes
    ATTR_CONFLICT_RES = Use List Attribute Values
    LIST_ATTR = _liste_mode_transp{}
    ELEMENTS -> ListExploder_heure
ListExploder_heure
    ATTR_ACCUM_MODE = Merge List Attributes
    ATTR_CONFLICT_RES = Use List Attribute Values
    LIST_ATTR = _liste_heures{}
    ELEMENTS -> Tester_NS_2
Tester_NS_2
    BOOL_OP = OR
    TEST_CLAUSE = TEST @Value(_orientation) = NS
    TEST_MODE = TEST
    PASSED -> TestFilter_auN_auS_2
    FAILED -> TestFilter_auE_auW_2
Note: positions relatives des tronçons à leur feu
TestFilter_auN_auS_2
    DEFAULT_VALUE = au_sud_du_feu
    PASSED_TEST_GROUP_OUTPUT = FIRST
    TEST_LIST = "BOOL_OP,OR,COMPOSITE_TEST,""""""1"""""",TEST_CLAUSE,TEST @Value(y_xmax) > @sub(@Value(_y_FEU),5)",au_nord_du_feu
    au_nord_du_feu -> AttributeCreator_compteN_2
    au_sud_du_feu -> AttributeCreator_compteS_2
AttributeCreator_compteN_2
    ATTR_TABLE = SET_TO compte_total = @int(@add(@Value(de_n.sum),@Value(vers_n.sum)))
    -> Junction_3
AttributeCreator_compteS_2
    ATTR_TABLE = SET_TO compte_total = @int(@add(@Value(de_s.sum) , @Value(vers_s.sum)))
    -> Junction_3
TestFilter_auE_auW_2
    DEFAULT_VALUE = a_ouest_du_feu
    PASSED_TEST_GROUP_OUTPUT = FIRST
    TEST_LIST = "BOOL_OP,OR,COMPOSITE_TEST,""""""1"""""",TEST_CLAUSE,TEST @Value(x.max) > @add(@Value(_x_FEU),5)",a_est_du_feu
    a_est_du_feu -> AttributeCreator_compteE_2
    a_ouest_du_feu -> AttributeCreator_compteW_2
AttributeCreator_compteE_2
    ATTR_TABLE = SET_TO compte_total = @int(@add(@Value(de_e.sum),@Value(vers_e.sum)))
    -> Junction_3
AttributeCreator_compteW_2
    ATTR_TABLE = SET_TO compte_total = @int(@add(@Value(de_o.sum),@Value(vers_o.sum)))
    -> Junction_3
Junction_3
    -> Reprojector_7

Bookmark: Voiture - camion
Voiture: Tester
    BOOL_OP = OR
    TEST_CLAUSE = TEST @Value(Description_Code_Banque) = Autos
    TEST_MODE = TEST
    PASSED -> troncons_compte_voitures (writer OGCGEOPACKAGE_2)
    PASSED -> troncons_compte_voitures (writer POSTGIS_1)
Camion: Tester
    BOOL_OP = OR
    TEST_CLAUSE:
      TEST @Value(Description_Code_Banque) = Camions articules
      TEST @Value(Description_Code_Banque) = Bus et Camions porteurs
      TEST @Value(Description_Code_Banque) = Camions Lourds
      TEST @Value(Description_Code_Banque) = Camions porteurs
    TEST_MODE = TEST
    PASSED -> troncons_compte_camions (writer OGCGEOPACKAGE_2)
    PASSED -> troncons_compte_camions (writer POSTGIS_1)

Bookmark: Collectif - actif
Bus: Tester
    BOOL_OP = OR
    TEST_CLAUSE = TEST @Value(Description_Code_Banque) = Bus
    TEST_MODE = TEST
    PASSED -> troncons_compte_bus (writer OGCGEOPACKAGE_2)
    PASSED -> troncons_compte_bus (writer POSTGIS_1)
Vélo: Tester
    BOOL_OP = OR
    TEST_CLAUSE = TEST @Value(Description_Code_Banque) = Velos
    TEST_MODE = TEST
    PASSED -> troncons_compte_velos (writer OGCGEOPACKAGE_2)
    PASSED -> troncons_compte_velos (writer POSTGIS_1)

Bookmark: Habilage de la carte
CARTO_DRA_EAU_JOUR (reader SHAPEFILE_1)
    attributes: ID number(11,0), TOPONYME varchar(200), EQM varchar(40), SOURCE varchar(30), TRAITEMENT varchar(30), DIFFUSEUR varchar(50), VERSION long
    -> AreaCalculator_2
AreaCalculator_2
    AREA_ATTR = _area
    AREA_TYPE = Plane Area
    MULT = 1
    -> Tester
Tester
    BOOL_OP = OR
    TEST_CLAUSE = TEST @Value(_area) > 105000
    TEST_MODE = TEST
    PASSED -> AttributeRemover
AttributeRemover
    REMOVE_ATTRS = ID
    -> Reprojector_10
limites-administratives-agglomeration-nad83 (reader SHAPEFILE_2)
    attributes: CODEID number(18,0), NOM varchar(80), NOM_OFFICI varchar(80), CODEMAMH varchar(80), CODE_3C varchar(80), NUM number(18,0), ABREV varchar(80), TYPE varchar(80), COMMENT varchar(129), DATEMODIF varchar(80)
    -> Reprojector
Reprojector
    DEST = EPSG:32188
    INTERPOLATION_TYPE_NAME = Nearest Neighbor
    RASTER_CELL_SIZE = Preserve Cells
    RASTER_TOLERANCE = 0.0
    REPROJECTED -> Tester_2
Tester_2
    BOOL_OP = OR
    TEST_CLAUSE = TEST @Value(TYPE) = Arrondissement
    TEST_MODE = TEST
    PASSED -> Reprojector_9
limites-terrestres (reader GEOJSON_5)
    attributes: DefaultAtt string
    -> Reprojector_5
Reprojector_5
    DEST = EPSG:32188
    INTERPOLATION_TYPE_NAME = Nearest Neighbor
    RASTER_CELL_SIZE = Preserve Cells
    RASTER_TOLERANCE = 0.0
    REPROJECTED -> Reprojector_8

Bookmark: Données de flux (attributaire)
Note: Somme les données de traffic par Id_intersection, date, heure, type de transport
